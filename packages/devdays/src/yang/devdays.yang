module devdays {
  yang-version 1.1;
  namespace "http://com/example/devdays";
  //namespace "http://tail-f.com";
  //Author:Nicklas Wagerth

  prefix devdays;

 revision 2022-02-01 {
   description "Starting all over" + "added actions input and output from attendee";
 } 

  identity format-idty{
    description "Root identity for all event formats";
  }
  identity live-idty {
    base format-idty;
  }
   identity hybrid-idty {
    base format-idty;
  }
   identity virtual-idty {
    base format-idty;
  }
  identity live-main-event {
    base live-idty;
  }
  identity live-event {
    base live-idty;
  }
  identity live-satellite {
    base live-idty;
  }
  identity hybrid-main-event {
    base hybrid-idty;
  }
  identity hybrid-event {
    base hybrid-idty;
  }
  identity virtual-remote {
    base virtual-idty;
  }

 grouping event-venue-format-ref{
  leaf event-name {
        type leafref {
          path /devdays-events/devdays-event/event-name;
        }
      }
      leaf venue-name {
        type leafref {
          path /venues/venue/format/venue-name;
        }
      }
      leaf format {
        type leafref {
          path /venues/venue/format/format-id;
        }
      }
 }

  notification ticket-delivery {
    leaf attendee {
      type leafref {
        path /devdays-attendees/devdays-attendee/first-name;
      }
    }
    uses event-venue-format-ref;
  }
 
  container devdays-events {      
    description "all you need to know about the event";

    list devdays-event {
      key event-name;
      leaf event-name {           //" e.g. Automation Developer Days 2020";
        type string;
      }
        leaf event-id {           //" GSMM event id"; 102531
          type string{
            length 6;
            pattern '[0-9]{6}';
            }
      }  
      leaf start-date {           //add format and restriction
        type string;
      }
      leaf event-length {
        type uint32 {
          range 1..5;
          } 
      }

      leaf event-type {
        type enumeration {
          enum "in-person";
          enum "hybrid";
          enum "virtual";
        }
      }
      
    }
  }

  container venues {
    list venue {
        key venue-name;
        leaf venue-name {
          mandatory true;
          type string;
        }
        leaf event-name{
          type leafref{
            path /devdays-events/devdays-event/event-name;
          }
        }
        leaf venue-id {            //unique id, 102531
            type string{
            length 2;
            pattern '[0-9]{2}';
            }
          }
        
        list format {
          key venue-name;     
          leaf venue-name{            
            type string;
          }
          
          leaf format-id {
            mandatory true;
            type identityref {
              base format-idty;
            }
          }
          leaf ticket-price {
            type uint32 {
            range 0..800;
            }
          }

          container number-of-seats {
            when 'not(derived-from(../format-id,  "devdays:virtual-idty"))';
            config false;
            leaf seats-left{
              type uint32;
            }
            leaf reserved {
              type uint32;
            }
            leaf available {
              type uint32;
            }
          }
        }
      }
  }
   
  container devdays-attendees {     //users

    list devdays-attendee {
        key email;

        leaf first-name {
          mandatory true;
          type string;  
        }
        leaf last-name {
          mandatory true;
          type string;
        }
        leaf company {
          mandatory true;
          type string;
        }
        leaf work-title {
          mandatory true;
          type string;
        }
        leaf email {          //restrict gmail.com and hotmail.com
          mandatory true;
          type string;
        } 
        // list event-history {
        //   config false;
        //   key "event-name venue-name format";
        //   uses 
        // }
        
        } 
      action checkout {         //inside list devday-attendee
        input {
          uses event-venue-format-ref;
          }

        output {
          choice outcome {
            case success {
              leaf success {
                type empty; 
                description "order received and will be sent to attendee";
              }
              leaf delivery-url {
                type string;
                description "link to ticket";
              }
            leaf no-seats-available {
              type empty;
              description "No seats available, a notification will be sent if seats are released";
            }
            leaf failure {
              type string;
              description "Order Canceled";
            }
            }
          }
        }
      }
    }

  container devdays-speakers {
    description "all registered speakers";
    list speaker {
      key session-title;

      leaf speaker-approved {
        type boolean;
      }
      leaf first-name {
        type leafref {
          path /devdays-attendees/devdays-attendee/first-name;
        }
      }
      leaf last-name {
        type leafref {
          path /devdays-attendees/devdays-attendee/last-name;
        }
      }
      leaf work-title {
        type leafref {
          path /devdays-attendees/devdays-attendee/work-title;
        }
      }
      leaf email {
        type leafref {
          path /devdays-attendees/devdays-attendee/email;
        }
      }

      leaf session-title {
        type string;
      }
      leaf segment {
        type enumeration{
          enum "true-stories";
          enum "nso-essentials";
        }
      }
      leaf subcategories {
        type enumeration{
          enum "scaling-out";
          enum "performance";

        }
      }
     

    }
  }
}
